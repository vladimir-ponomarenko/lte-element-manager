module _3gpp-common-managed-element {
  yang-version 1.1;

  namespace "urn:3gpp:sa5:_3gpp-common-managed-element";
  prefix cme;

  import ietf-inet-types {
    prefix inet;
  }

  organization "SibSUTIS & YADRO";
  description
    "Common Managed Element model.

     This module defines the managed object hierarchy and operational PM
     measurements exposed northbound via NETCONF/YANG.";

  revision 2026-04-15 {
    description "Initial NRM + PM subset for EMS agent.";
  }

  typedef id-string {
    type string {
      length "1..128";
    }
    description "Generic MO identifier (config key).";
  }

  grouping measurements-group {
    description "Minimal PM measurements container (operational).";
    container measurements {
      config false;

      leaf throughputDL {
        type decimal64 { fraction-digits 6; }
        units "bps";
      }

      leaf throughputUL {
        type decimal64 { fraction-digits 6; }
        units "bps";
      }

      leaf sinrUL {
        type decimal64 { fraction-digits 6; }
        units "dB";
      }

      leaf cqiDL {
        type decimal64 { fraction-digits 6; }
        units "index";
      }
    }
  }

  list SubNetwork {
    key "id";
    description "Top-level SubNetwork.";

    leaf id {
      type id-string;
      config true;
    }

    list ManagedElement {
      key "id";
      description "ManagedElement (NRM root).";

      leaf id {
        type id-string;
        config true;
      }

      list ENBFunction {
        key "id";
        description "LTE eNB function.";

        leaf id {
          type id-string;
          config true;
        }

        leaf enb_id {
          type string {
            length "1..64";
          }
          config true;
          description
            "Global eNB identifier.";
        }

        leaf mcc {
          type string {
            pattern '[0-9]{3}';
          }
          config true;
          description "Mobile Country Code.";
        }

        leaf mnc {
          type string {
            pattern '[0-9]{2,3}';
          }
          config true;
          description "Mobile Network Code.";
        }

        leaf n_prb {
          type uint16;
          must ". = 6 or . = 15 or . = 25 or . = 50 or . = 75 or . = 100";
          config true;
          description "Cell bandwidth in PRBs.";
        }

        leaf mme_addr {
          type inet:ip-address;
          config true;
          description "MME address for S1-C.";
        }

        leaf gtp_bind_addr {
          type inet:ip-address;
          config true;
          description "Local bind address for S1-U GTP-U.";
        }

        leaf s1c_bind_addr {
          type inet:ip-address;
          config true;
          description "Local bind address for S1-C S1AP.";
        }

        leaf s1c_bind_port {
          type uint16 {
            range "0..65535";
          }
          config true;
          description "Local bind port for S1-C (0 means ephemeral).";
        }

        leaf tm {
          type uint8 {
            range "1..4";
          }
          config true;
          description "Transmission mode (TM1..TM4).";
        }

        list EUtranCell {
          key "id";
          description "E-UTRAN cell managed object.";

          leaf id {
            type id-string;
            config true;
          }

          leaf tac {
            type string {
              length "1..16";
            }
            config true;
            description "Tracking Area Code (e.g. 0x0007).";
          }

          leaf dl_earfcn {
            type uint32 {
              range "0..262143";
            }
            config true;
            description "Configured LTE downlink EARFCN.";
          }

          leaf pci {
            type uint16 {
              range "0..503";
            }
            config true;
            description "Physical Cell Identifier.";
          }

          leaf ho_active {
            type boolean;
            config true;
            description "Enable/disable handover logic.";
          }

          leaf a3_offset {
            type int16;
            config true;
            description "Event A3 offset (dB).";
          }

          leaf time_to_trigger {
            type uint16;
            config true;
            description "Event A3 time-to-trigger (ms).";
          }

          leaf hysteresis {
            type int16;
            config true;
            description "Measurement reporting hysteresis (dB).";
          }

          uses measurements-group;
        }
      }
    }
  }
}
